--------------------------------------------------------------------------------
--
-- AsnCC 2.0 test.
--
-- Based on ANSI41 (simplified types). Non LRF format.
--
--------------------------------------------------------------------------------

TEST1 DEFINITIONS IMPLICIT TAGS ::=

BEGIN

AuthenticationFailureReportRRL ::= SET
{
    authenticationAlgorithmVersion [77] IMPLICIT OCTET STRING (SIZE(1)) OPTIONAL,

    denyAccess [50] IMPLICIT ENUMERATED
    { 
        notUsed (0),
        unspecified (1),
        sSDUpdateFailure (2) 
    } OPTIONAL,

    randomVariableSSD [42] IMPLICIT OCTET STRING (SIZE(7)) OPTIONAL
}

END
