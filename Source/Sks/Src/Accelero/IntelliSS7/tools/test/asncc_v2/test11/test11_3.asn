--------------------------------------------------------------------------------
--
-- AsnCC 2.0 test.
--
-- Based on GSM MAP. Merge test.
--
--------------------------------------------------------------------------------

-- TEST11-3.


TEST11-3 DEFINITIONS ::=

BEGIN

TeleserviceCode ::= OCTET STRING (SIZE(1))

TeleserviceList ::= SEQUENCE SIZE(1..22) OF TeleserviceCode

END
