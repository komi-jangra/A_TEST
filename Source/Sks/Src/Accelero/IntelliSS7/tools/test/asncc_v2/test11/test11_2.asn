--------------------------------------------------------------------------------
--
-- AsnCC 2.0 test.
--
-- Based on GSM MAP. Merge test.
--
--------------------------------------------------------------------------------

-- TEST11-2.


TEST11-2 DEFINITIONS ::=

BEGIN

TeleserviceCode ::= OCTET STRING (SIZE(1))

TeleserviceList ::= SEQUENCE SIZE(1..20) OF TeleserviceCode

END
