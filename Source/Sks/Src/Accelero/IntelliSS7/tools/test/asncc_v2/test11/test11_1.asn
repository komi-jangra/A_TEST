--------------------------------------------------------------------------------
--
-- AsnCC 2.0 test.
--
-- Based on GSM MAP. Merge test.
--
--------------------------------------------------------------------------------

-- TEST11-1.


TEST11-1 DEFINITIONS ::=

BEGIN

TeleserviceCode ::= OCTET STRING (SIZE(1))

TeleserviceList ::= SEQUENCE SIZE(1..20) OF TeleserviceCode

END
