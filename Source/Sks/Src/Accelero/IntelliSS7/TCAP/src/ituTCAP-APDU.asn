--
-- DEFINITIONS IMPLICIT TAGS ::=
--* ITU-Q.773-TCAP(3) *-- ITU-TCAP-APDU DEFINITIONS ::=
--

BEGIN

--
-- Associate Result
--
Associate-result ::= INTEGER {
    accepted(0),
    reject-permanent(1)
}

--
-- Associate source diagnostic
--
Associate-source-diagnostic ::= CHOICE {
    dialogue-service-user        [1] INTEGER {
        null(0),
        no-reason-given(1),
        application-context-name-not-supported(2)
    },
    dialogue-service-provider    [2] INTEGER {
        null(0),
        no-reason-given(1),
        no-common-dialogue-portion(2)
    }
}

--
-- Release request reason
--
Release-request-reason ::= INTEGER {
   normal(0),
   urgent(1),
   user-defined(30)
}

--
-- Release response reason
--
Release-response-reason ::= INTEGER {
    normal(0),
    not-finished(1),
    user-defined(30)
}

--
-- ABRT source
--
ABRT-source ::= INTEGER {
    dialogue-service-user(0),
    dialogue-service-provider(1)
}

--
-- Application Context
--
ApplicationContext ::= OBJECT IDENTIFIER

--
-- User Information
--
UserInformation ::= SEQUENCE OF ANY

--
-- AARQ APDU
--
AARQ-apdu ::= [APPLICATION 0] IMPLICIT SEQUENCE {
    protocol-version            [0] IMPLICIT BIT STRING { version1(0) } OPTIONAL,
--                                  DEFAULT { version1 },
    application-context-name    [1] ApplicationContext,
    user-information            [30] IMPLICIT UserInformation OPTIONAL
}

--
-- AARE APDU
--
AARE-apdu ::= [APPLICATION 1] IMPLICIT SEQUENCE {
    protocol-version            [0] IMPLICIT BIT STRING { version1(0) } OPTIONAL,
--                                  DEFAULT { version1 },
    application-context-name    [1] ApplicationContext,
    result                      [2] Associate-result,
    result-source-diagnostic    [3] Associate-source-diagnostic,
    user-information            [30] IMPLICIT UserInformation OPTIONAL
}

--
-- RLRQ APDU (not used)
--
RLRQ-apdu ::= [APPLICATION 2] IMPLICIT SEQUENCE {
    reason                      [0] IMPLICIT Release-request-reason OPTIONAL,
    user-information            [30] IMPLICIT UserInformation OPTIONAL
}

--
-- RLRE APDU (not used)
--
RLRE-apdu ::= [APPLICATION 3] IMPLICIT SEQUENCE {
    reason                      [0] IMPLICIT Release-response-reason OPTIONAL,
    user-information            [30] IMPLICIT UserInformation OPTIONAL
}

--
-- ABRT APDU
--
ABRT-apdu ::= [APPLICATION 4] IMPLICIT SEQUENCE {
    abort-source                [0] IMPLICIT ABRT-source,
    user-information            [30] IMPLICIT UserInformation OPTIONAL
}

--
-- Dialogue PDU
--
DialoguePDU ::= CHOICE {
    dialogueRequest   AARQ-apdu,
    dialogueResponse  AARE-apdu,
    dialogueAbort     ABRT-apdu
}

--
-- dialogue as id
--
-- dialogue-as-id OBJECT IDENTIFIER ::= { ccitt recommendation q 773 as (1)
--                                        dialogue-as (1) version1 (1) }

--
-- AUDT APDU
--
AUDT-apdu ::= [APPLICATION 0] IMPLICIT SEQUENCE {
    protocol-version            [0] IMPLICIT BIT STRING { version1(0) } OPTIONAL,
--                                  DEFAULT { version1 },
    application-context-name    [1] OBJECT IDENTIFIER,
    user-information            [30] IMPLICIT UserInformation OPTIONAL
}

--
-- Unidialogue PDU
--
UniDialoguePDU ::= CHOICE {
    unidialoguePDU    AUDT-apdu
}

END
